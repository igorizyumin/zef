[DOCUMENT]
TITLE: ZEF IMPLEMENTATION — selected solution and code work
UID: ZEF-IMPLEMENTATION-DOC
VERSION: 1.1.0
DATE: 2026-10-11
PREFIX: ZEF-IMP
ROOT: False
OPTIONS:
  ENABLE_MID: False
  MARKUP: Text

[TEXT]
STATEMENT: >>>
IMPLEMENTATION items record concrete mechanisms present in the current source
tree. The statements describe the code as written, including deliberately
unfinished target ports and the current verification boundary. Code references
are recorded as File relations and, where useful, repeated in comments for
readability. These records are descriptive implementation notes rather than
additional behavioral requirements.
<<<

[[SECTION]]
TITLE: Build, configuration, and common failure handling

[REQUIREMENT]
UID: ZEF-IMP-001
TITLE: Configuration defaults and compile-time guards
STATEMENT: >>>
``include/zef_config.h`` supplies defaults for reactor slots, topic count,
message-pool count, state depth, mailbox capacity, tick type, pool alignment,
assertion mode, claim-counter type, and execution model. ``ZEF_ENABLE_ASSERTIONS``
defaults to enabled and controls only ``ZEF_REQUIRE`` precondition checks;
direct ``ZEF_PANIC`` calls for runtime consistency and resource conditions
remain active. The CMake option with the same name exposes this switch for
complete builds. When disabled, invalid caller inputs are outside the API
contract. Preprocessor checks constrain the configured ranges and execution-
model values. Cooperative mode is the default; preemptive mode is a complete-
build choice for a target Port.
Static assertions check the alignment and the selected integer widths.
``ZefMaxAlign`` provides the maximum scalar alignment used by the default pool
alignment expression on the supported host compilers.
<<<
COMMENT: Code references: include/zef_config.h; include/zef.h.
RELATIONS:
- TYPE: Parent
  VALUE: ZEF-IF-004
- TYPE: File
  FORMAT: Sourcecode
  PATH: include/zef_config.h
- TYPE: File
  FORMAT: Sourcecode
  PATH: include/zef.h

[REQUIREMENT]
UID: ZEF-IMP-002
TITLE: Complete public runtime structures
STATEMENT: >>>
``include/zef.h`` exposes complete definitions for the pool, Message, Mailbox,
Machine, Reactor, Kernel, TopicTable, Clock, Timer, and Port structures. The
framework marks its internal members as reserved in comments rather than using
opaque handles. Caller-owned storage appears directly in the public structures
and in the Mailbox slot-array arguments.
<<<
COMMENT: Code reference: include/zef.h. The implementation uses one public umbrella header rather than separate opaque type and API headers.
RELATIONS:
- TYPE: Parent
  VALUE: ZEF-IF-001
- TYPE: Parent
  VALUE: ZEF-IF-003
- TYPE: File
  FORMAT: Sourcecode
  PATH: include/zef.h

[REQUIREMENT]
UID: ZEF-IMP-003
TITLE: Panic boundary and ordinary results
STATEMENT: >>>
``ZResult``, ``ZPanicReason``, and ``ZPanicInfo`` are declared in
``include/zef.h``. Fatal framework checks use ``ZEF_PANIC`` directly or
``ZEF_REQUIRE`` for conditional checks; both capture the framework source
location before calling the externally supplied non-returning ``z_panic``
function. The library does not provide a default panic implementation; the
host smoke test supplies an aborting handler. Expected empty, not-running, and
not-found observations use ``ZResult`` while invalid arguments, lifecycle
violations, ownership failures, resource exhaustion, and state errors route
through the panic boundary.
<<<
COMMENT: Code references: include/zef.h; src/zef_message.c; tests/zef_smoke_test.c.
RELATIONS:
- TYPE: Parent
  VALUE: ZEF-IF-002
- TYPE: File
  FORMAT: Sourcecode
  PATH: include/zef.h
- TYPE: File
  FORMAT: Sourcecode
  PATH: src/zef_message.c
- TYPE: File
  FORMAT: Sourcecode
  PATH: tests/zef_smoke_test.c

[REQUIREMENT]
UID: ZEF-IMP-004
TITLE: Host build and smoke-test target
STATEMENT: >>>
The root ``CMakeLists.txt`` builds a static ``zef`` library from five C11 source
files, exports ``include`` as its public include directory, enables warning
options, and registers one CTest executable named ``zef_smoke_test``. The
current build contains Debug and Release host configurations; no separate
configuration-fixture target appears in the repository.
<<<
COMMENT: Code references: CMakeLists.txt; tests/zef_smoke_test.c.
RELATIONS:
- TYPE: Parent
  VALUE: ZEF-IF-050
- TYPE: File
  FORMAT: Sourcecode
  PATH: CMakeLists.txt
- TYPE: File
  FORMAT: Sourcecode
  PATH: tests/zef_smoke_test.c

[[/SECTION]]

[[SECTION]]
TITLE: Message, Mailbox, and Machine implementation

[REQUIREMENT]
UID: ZEF-IMP-010
TITLE: Fixed message pools and embedded envelope
STATEMENT: >>>
``src/zef_message.c`` initializes caller-provided aligned block storage as a
free list. Allocation selects the smallest initialized pool whose block size
contains ``sizeof(ZMsg) + payload_size``; equal sizes retain array order.
The allocated block begins with a complete ``ZMsg`` and places the
payload immediately after it. ``z_message_begin`` creates a dynamic Message
with one creator reference. ``z_message_static_init`` represents an immutable
caller-owned Message without a pool block.
<<<
COMMENT: Code references: include/zef.h; src/zef_message.c.
RELATIONS:
- TYPE: Parent
  VALUE: ZEF-IF-010
- TYPE: Parent
  VALUE: ZEF-IF-012
- TYPE: File
  FORMAT: Sourcecode
  PATH: include/zef.h
- TYPE: File
  FORMAT: Sourcecode
  PATH: src/zef_message.c

[REQUIREMENT]
UID: ZEF-IMP-011
TITLE: Message lifecycle and claim accounting
STATEMENT: >>>
Dynamic Messages begin with one creator reference. A consuming Mailbox post or
topic publication transfers that reference to the framework and nulls the
sender pointer. Retain increments the reference counter, release decrements it, and the final release returns the block
to its originating pool. Static Messages bypass claim changes and pool
reclamation. Checked mutable and read-only accessors verify the lifecycle and,
for typed access, the exact payload size.
<<<
COMMENT: Code references: src/zef_message.c; src/zef_mailbox.c; src/zef_kernel.c.
RELATIONS:
- TYPE: Parent
  VALUE: ZEF-IF-010
- TYPE: Parent
  VALUE: ZEF-IF-011
- TYPE: File
  FORMAT: Sourcecode
  PATH: src/zef_message.c
- TYPE: File
  FORMAT: Sourcecode
  PATH: src/zef_mailbox.c
- TYPE: File
  FORMAT: Sourcecode
  PATH: src/zef_kernel.c

[REQUIREMENT]
UID: ZEF-IMP-012
TITLE: Monotonic ring Mailbox
STATEMENT: >>>
``src/zef_mailbox.c`` stores caller-provided Message-pointer slots behind
monotonic ``head`` and ``tail`` counters. Normal posts consume a dynamic
Message, front posts decrement the head, and postpone retains an existing
Message before enqueueing it. Take transfers the queued reference to the
caller. Occupancy, free-space, minimum-free-space, and predicate-based stable
removal operate directly on the bounded ring without general-purpose
allocation.
<<<
COMMENT: Code references: include/zef.h; src/zef_mailbox.c.
RELATIONS:
- TYPE: Parent
  VALUE: ZEF-IF-013
- TYPE: File
  FORMAT: Sourcecode
  PATH: include/zef.h
- TYPE: File
  FORMAT: Sourcecode
  PATH: src/zef_mailbox.c

[REQUIREMENT]
UID: ZEF-IMP-013
TITLE: Timer-private messages and mailbox layout
STATEMENT: >>>
Each public ``ZMailbox`` stores only its configured Message pointer slots.
Timers create or embed a private Message and enqueue that same Message for
each expiration. Stop-with-clear and destruction remove matching private
Message pointers using the bounded mailbox removal operation, so no per-slot
timer owner metadata or dynamic allocation is required.
<<<
COMMENT: Code references: include/zef.h; src/zef_mailbox.c; src/zef_timer.c.
RELATIONS:
- TYPE: Parent
  VALUE: ZEF-IF-013
- TYPE: Parent
  VALUE: ZEF-IF-032
- TYPE: File
  FORMAT: Sourcecode
  PATH: include/zef.h
- TYPE: File
  FORMAT: Sourcecode
  PATH: src/zef_mailbox.c
- TYPE: File
  FORMAT: Sourcecode
  PATH: src/zef_timer.c

[REQUIREMENT]
UID: ZEF-IMP-020
TITLE: Descriptor-based Machine
STATEMENT: >>>
State descriptors remain caller-owned ``ZStateNode`` objects containing parent,
initial, handler, enter, and leave links. ``ZMachine`` stores the root, current
node, application context, and lifecycle flags. Dispatch walks parent links
until a handler handles the Message or requests a transition. Transition code
uses fixed-size local path arrays bounded by ``Z_MAX_STATE_DEPTH`` and invokes
leave hooks from the source toward the common ancestor, then enter hooks toward
the target.
<<<
COMMENT: Code references: include/zef.h; src/zef_machine.c.
RELATIONS:
- TYPE: Parent
  VALUE: ZEF-IF-020
- TYPE: Parent
  VALUE: ZEF-IF-021
- TYPE: File
  FORMAT: Sourcecode
  PATH: include/zef.h
- TYPE: File
  FORMAT: Sourcecode
  PATH: src/zef_machine.c

[REQUIREMENT]
UID: ZEF-IMP-021
TITLE: Runtime state consistency validation
STATEMENT: >>>
Machine initialization checks the non-null root, root-parent relationship, and
parent cycles. Runtime startup and transition validation check initial-child
relationships and that transition targets reach the configured root within the
depth limit.
Startup and dispatch track explicit lifecycle flags; startup enters the root
and follows initial links, while a self-transition leaves and re-enters the
current node before following its initial links.
<<<
COMMENT: Code reference: src/zef_machine.c.
RELATIONS:
- TYPE: Parent
  VALUE: ZEF-IF-020
- TYPE: File
  FORMAT: Sourcecode
  PATH: src/zef_machine.c

[REQUIREMENT]
UID: ZEF-IMP-030
TITLE: Permanent Reactor registry and lifecycle
STATEMENT: >>>
``src/zef_kernel.c`` assigns each initialized Reactor an explicit zero-based
slot in the Kernel registry. The slot is also the Reactor's strict priority;
the high-water registry bound allows temporary gaps. Registration attaches the
Reactor Mailbox to the Kernel, and start marks the Reactor active and starts
its primary Machine. Registered Reactors remain in the registry for the Kernel
lifetime. The source tree contains no Reactor stop, removal, cleanup, or
terminated-stack path.
<<<
COMMENT: Code references: include/zef.h; src/zef_kernel.c.
RELATIONS:
- TYPE: Parent
  VALUE: ZEF-IF-022
- TYPE: File
  FORMAT: Sourcecode
  PATH: include/zef.h
- TYPE: File
  FORMAT: Sourcecode
  PATH: src/zef_kernel.c

[[/SECTION]]

[[SECTION]]
TITLE: Actor composition

[REQUIREMENT]
UID: ZEF-IMP-031
TITLE: Actor convenience implementation
STATEMENT: >>>
``src/zef_actor.c`` initializes a caller-owned ``ZActor`` by composing its
embedded Machine, Mailbox, and Reactor in dependency order. The implementation
passes through the application's state root, context, and Mailbox slot storage,
then forwards registration and start to the existing Reactor APIs. It performs
no allocation and adds no scheduler state.
<<<
COMMENT: Code references: include/zef.h; src/zef_actor.c; tests/zef_test_work.c.
RELATIONS:
- TYPE: Parent
  VALUE: ZEF-IF-023
- TYPE: File
  FORMAT: Sourcecode
  PATH: include/zef.h
- TYPE: File
  FORMAT: Sourcecode
  PATH: src/zef_actor.c
- TYPE: File
  FORMAT: Sourcecode
  PATH: tests/zef_test_work.c

[[/SECTION]]

[[SECTION]]
TITLE: Kernel, topics, and time

[REQUIREMENT]
UID: ZEF-IMP-040
TITLE: Cooperative Kernel runnable bitmap
STATEMENT: >>>
The Kernel stores one 32-bit runnable bitmap indexed by explicit zero-based
Reactor identity. Reactor identity is also strict priority, with larger
identities running first; unregistered identities may be gaps. Mailbox changes
set or clear a Reactor bit when its primary Reactor is started.
``z_kernel_run_one`` scans runnable identities from high to low, takes one
Message, dispatches the primary Machine, releases the dispatch claim, and
refreshes the bit.
``z_kernel_run_forever`` calls the Port idle callback after a no-work result.
<<<
COMMENT: Code references: include/zef.h; src/zef_kernel.c.
RELATIONS:
- TYPE: Parent
  VALUE: ZEF-IF-030
- TYPE: File
  FORMAT: Sourcecode
  PATH: include/zef.h
- TYPE: File
  FORMAT: Sourcecode
  PATH: src/zef_kernel.c

[REQUIREMENT]
UID: ZEF-IMP-050
TITLE: Bitmap topic table and ordered publication
STATEMENT: >>>
``ZTopicTable`` stores one 32-bit subscriber bitmap per configured topic and a
pointer to its Kernel. Subscription changes and publication snapshots enter
and leave the Port critical section. Publication consumes the sender pointer,
snapshots subscribers, then scans Reactor identities from high to low and
enqueues the same Message in strict priority order while retaining references
for later recipients. The dense case uses the high-water identity bound
and does not allocate or sort a recipient list; unregistered identity gaps are
skipped by the bitmap.
<<<
COMMENT: Code references: include/zef.h; src/zef_kernel.c.
RELATIONS:
- TYPE: Parent
  VALUE: ZEF-IF-031
- TYPE: File
  FORMAT: Sourcecode
  PATH: include/zef.h
- TYPE: File
  FORMAT: Sourcecode
  PATH: src/zef_kernel.c

[REQUIREMENT]
UID: ZEF-IMP-060
TITLE: Linked-list Clock service
STATEMENT: >>>
The Clock keeps a caller-owned linked list with head and tail pointers rather
than a delta list. Arming appends a Timer and stores an absolute modular due
tick. Each clock tick advances the counter and scans the list for timers whose
due tick equals the current tick. Periodic timers are unlinked and appended at
their next due tick, preserving list order for same-tick expiry. Expiry only
enqueues a Message; it does not invoke application handlers.
<<<
COMMENT: Code references: include/zef.h; src/zef_timer.c.
RELATIONS:
- TYPE: Parent
  VALUE: ZEF-IF-032
- TYPE: File
  FORMAT: Sourcecode
  PATH: include/zef.h
- TYPE: File
  FORMAT: Sourcecode
  PATH: src/zef_timer.c

[REQUIREMENT]
UID: ZEF-IMP-061
TITLE: Timer-owned messages and base claims
STATEMENT: >>>
Payload timer initialization allocates and copies one private dynamic Message
for the Timer. Expiry retains one claim per queued delivery, while the Timer
keeps its base claim until destruction. Stopping or one-shot expiry leaves the
base claim in place so the Timer can be armed again. Stop-with-clear unlinks
the Timer and removes matching private Message entries while preserving the
base claim. Destruction unlinks the Timer, removes matching private Message
entries, and releases the retained base claim. Topic timers use an embedded
zero-payload static Message and do not use pool claims.
<<<
COMMENT: Code references: src/zef_timer.c; src/zef_mailbox.c.
RELATIONS:
- TYPE: Parent
  VALUE: ZEF-IF-032
- TYPE: File
  FORMAT: Sourcecode
  PATH: src/zef_timer.c
- TYPE: File
  FORMAT: Sourcecode
  PATH: src/zef_mailbox.c

[[/SECTION]]

[[SECTION]]
TITLE: Ports, optional preemption, and verification

[REQUIREMENT]
UID: ZEF-IMP-070
TITLE: Port callback boundary
STATEMENT: >>>
The target port supplies global ``z_port_critical_enter`` and
``z_port_critical_leave`` operations for processor-wide interrupt exclusion.
``ZPort`` is a public callback structure containing only the Kernel-specific
reschedule request and idle operations. Kernel, TopicTable, Mailbox, and
Message-pool code use the global critical operations; unregistered Mailboxes
and standalone Message pools are therefore protected as well. The generic
library supplies a no-op host default, while a target port overrides the
critical functions with strong definitions.
<<<
COMMENT: Code references: include/zef.h; src/zef_kernel.c; tests/zef_smoke_test.c.
RELATIONS:
- TYPE: Parent
  VALUE: ZEF-IF-040
- TYPE: File
  FORMAT: Sourcecode
  PATH: include/zef.h
- TYPE: File
  FORMAT: Sourcecode
  PATH: src/zef_kernel.c
- TYPE: File
  FORMAT: Sourcecode
  PATH: tests/zef_smoke_test.c

[REQUIREMENT]
UID: ZEF-IMP-071
TITLE: Cortex-M0 shared-stack port plan
STATEMENT: >>>
The initial Cortex-M0/M0+ Port source now provides global PRIMASK critical sections,
PendSV rescheduling, WFI idle, and shared-stack exception entry and return.
Target startup/vector integration and hardware validation remain later-phase
work. The selected design is a shared-stack activation port: Reactor handlers
execute on one MSP stack, higher-priority ready Reactors nest through deferred
exception activation, and no Reactor receives process-stack storage. The
the scheduler-only ``ZPort`` callback shape remains the target-neutral boundary; target
exception entry and return are private port implementation details.
<<<
COMMENT: Code references: ``ports/arm-cm0p/zef_arm_cm0p_port.c`` and ``ports/arm-cm0p/zef_arm_cm0p_port.h``. Startup, vector, linker-stack, and hardware validation work remains.
RELATIONS:
- TYPE: Parent
  VALUE: ZEF-IF-040
- TYPE: Parent
  VALUE: ZEF-IF-042
- TYPE: File
  FORMAT: Sourcecode
  PATH: ports/arm-cm0p/zef_arm_cm0p_port.c
- TYPE: File
  FORMAT: Sourcecode
  PATH: ports/arm-cm0p/zef_arm_cm0p_port.h

[REQUIREMENT]
UID: ZEF-IMP-072
TITLE: Shared-stack activation status
STATEMENT: >>>
No per-Reactor process stacks or callee-saved register switching appear in the
current tree. The scheduler's portable activation path tracks whether a newly
runnable Reactor can preempt the active priority and provides an internal
higher-priority activation entry point. The target Port now supplies the
exception-frame boundary; the build-time execution mode controls whether its
PendSV activation machinery is emitted. Cooperative mode remains the default.
<<<
COMMENT: Code references: ``src/zef_kernel.c`` and ``src/zef_internal.h``.
RELATIONS:
- TYPE: Parent
  VALUE: ZEF-IF-040
- TYPE: Parent
  VALUE: ZEF-IF-042
- TYPE: File
  FORMAT: Sourcecode
  PATH: src/zef_kernel.c
- TYPE: File
  FORMAT: Sourcecode
  PATH: src/zef_internal.h

[REQUIREMENT]
UID: ZEF-IMP-074
TITLE: Shared-stack target assembly boundary
STATEMENT: >>>
The Cortex-M0/M0+ port shall use a naked PendSV entry to defer activation
until the last nested interrupt exits, synthesize a valid exception frame to
enter the Kernel activation routine in Thread mode, and use an NMI or reserved
IRQ return path to resume the interrupted shared-stack activation. The port
shall use ``PRIMASK`` rather than ``BASEPRI`` and shall preserve the Armv6-M
exception-frame alignment and Thumb-state requirements.
<<<
COMMENT: The exception boundary is implemented in ``ports/arm-cm0p/zef_arm_cm0p_port.c``; target startup integration and hardware validation are not yet complete.
RELATIONS:
- TYPE: Parent
  VALUE: ZEF-IF-042
- TYPE: File
  FORMAT: Sourcecode
  PATH: ports/arm-cm0p/zef_arm_cm0p_port.c

[REQUIREMENT]
UID: ZEF-IMP-073
TITLE: Interrupt-context classification status
STATEMENT: >>>
The public API is exposed in ``include/zef.h`` and its interrupt-context
classification is described in ``docs/api-requirements.sdoc``. The current C
headers contain no compiler annotations or separately named ISR variants; the
implementation relies on the bounded fixed-storage code paths and the
documented caller context.
<<<
COMMENT: Code and documentation references: include/zef.h; docs/api-requirements.sdoc.
RELATIONS:
- TYPE: Parent
  VALUE: ZEF-IF-041
- TYPE: File
  FORMAT: Sourcecode
  PATH: include/zef.h
- TYPE: File
  FORMAT: Sourcecode
  PATH: docs/api-requirements.sdoc

[REQUIREMENT]
UID: ZEF-IMP-080
TITLE: Current consumer and behavior tests
STATEMENT: >>>
``tests/zef_smoke_test.c`` and ``tests/zef_test_work.c`` include the public
header and link the built library. The smoke executable covers the compact
end-to-end path. The traceable test-work executable covers public compilation,
pool selection, typed access, claims, panic reasons and preserved failure
state, Mailbox ordering and wraparound, hierarchical Machine transitions,
Reactor startup and cooperative scheduling, topic publication and
zero-recipient reclamation, Timer delivery and ownership, stop/clear/destroy, and
Port callback paths. The CMake test targets run both executables in the
available host configurations. Configuration-variant, property, and sanitizer
matrices remain outside the current host test target.
<<<
COMMENT: Code references: CMakeLists.txt; tests/zef_smoke_test.c; tests/zef_test_work.c; docs/test-work.sdoc.
RELATIONS:
- TYPE: Parent
  VALUE: ZEF-IF-050
- TYPE: File
  FORMAT: Sourcecode
  PATH: CMakeLists.txt
- TYPE: File
  FORMAT: Sourcecode
  PATH: tests/zef_smoke_test.c
- TYPE: File
  FORMAT: Sourcecode
  PATH: tests/zef_test_work.c
- TYPE: File
  FORMAT: Sourcecode
  PATH: docs/test-work.sdoc

[[/SECTION]]
